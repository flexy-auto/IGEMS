;2022-11-04 Moved Analyze to be to the left of Cleanup on Tools/Cam Tools
;2022-08-25 Added new sheet buttons for register
;2023-02-06 Updated IGEMS pulldown menu for reorganized selections About and Changelog and Check for updates
; 2024.06.12 - Cleaning up Sheets menus mostly.
; 2024.06.12 - added "Add other objects" command
; 2024.08.06 - added bevel cut commnad
;2024.10.02 - added Bevel2D icon
;2024.10.9 - added WARDJet tab with links to training videos
;2024.11.01 - more video links
;2024.11.14 - more links
;2024.11.22 - DeletePartsOnSheet, DeleteCutOrders, CenterPartsOnSheet apps
;2024.12.05 - Added Circle Cut command
;2025.01.21 - changed location of CSVtoOrganizer LSP

;;;;;;;;;;;;;;;;;;;;;;;;;;;;;;;;;;;;;;;;
;          Create system menu          ;
;;;;;;;;;;;;;;;;;;;;;;;;;;;;;;;;;;;;;;;;
;(SETQ ltfspar ltf) (DEFUN ltf (txt) (IF (NOT (MEMBER txt ltflist)) (SETQ ltflist (CONS txt ltflist))) (LTFSPAR txt))
;(DEFUN ltfsave () (ALERT "Saving")(SETQ fw (OPEN (STRCAT (GETVAR  "PATHROOT") "/LSP/TRANS.TXT") "w"))(FOREACH s (REVERSE ltflist) (WRITE-LINE s fw))  (CLOSE fw))
(SETQ submnu (TB-SYSBTN (LTF "New") "CORE.New.png" "CORE.New" "Ctrl+N"))
    (TB-BTN submnu (LTF "New") "CORE.New.png" "CORE.New" "Ctrl+N")
    (TB-BTN submnu (LTF "Templates") "CORE.Templates.png" "CORE.Templates" nil)
    (TB-BTN submnu (LTF "Drawing note") "CORE.DrawingNote.png" "CORE.DrawingNote" nil)

(SETQ submnu (TB-SYSBTN (LTF "Open") "CORE.Open.png" "CORE.Open" "Ctrl+O"))
    (TB-BTN submnu (LTF "Open") "CORE.Open.png" "CORE.Open" "Ctrl+O")
    (TB-BTN submnu (LTF "Samples") "CORE.OpenSamples.png" "CORE.OpenSamples" nil)
    (TB-BTN submnu (LTF "Import") "CAD.Import.png" "CAD.Import" "Ctrl+I")
    (TB-BTN submnu (LTF "Recover") "CORE.Recover.png" "CORE.Recover" nil)

(TB-SYSRECENT "CORE.Recentfiles.png") ;recent files special item

(TB-SYSBTN (LTF "Save") "CORE.Save.png" "CORE.Save" "Ctrl+S")

(SETQ submnu (TB-SYSBTN (LTF "Save as") "CORE.SaveAs.png" "CORE.SaveAs" "Ctrl+O"))
    (TB-BTN submnu (LTF "Save as") "CORE.SaveAs.png" "CORE.SaveAs" "Ctrl+Shift+S")
    (TB-BTN submnu (LTF "Save as template") "CORE.SaveTemplate.png" "CORE.SaveTemplate" nil)
    (TB-BTN submnu (LTF "Export") "CORE.Export.png" "CORE.Export" "Ctrl+E")
	(TB-BTN submnu (LTF "Support") "Cam2d2.BugReport.png" "Cam2d2.BugReportSave" nil)

(SETQ submnu (TB-SYSBTN (LTF "Close") "CORE.Close.png" "CORE.Close" "Ctrl+F4"))
    (TB-BTN submnu (LTF "Close") "CORE.Close.png" "CORE.Close" "Ctrl+F4")
    (TB-BTN submnu (LTF "Close all") "CORE.CloseAll.png" "CORE.CloseAll" nil)

(TB-SYSBTN "-") ;separator

(SETQ submnu (TB-SYSBTN (LTF "Plot") "CORE.Plot.png" "CORE.Plot" "Ctrl+P"))
    (TB-BTN submnu (LTF "Plot") "CORE.Plot.png" "CORE.Plot" "Ctrl+P")
    (TB-BTN submnu (LTF "Limits") "CORE.Limits.png" "CORE.Limits" nil)
    (TB-BTN submnu (LTF "Dump image") "CORE.DumpImage.png" "CORE.DumpImage" "Ctrl+G")

(SETQ submnu (TB-SYSBTN (LTF "Preferences") "CORE.Preferences.png" "CORE.Preferences" nil))
    (TB-BTN submnu (LTF "Preferences") "CORE.Preferences.png" "CORE.Preferences" nil)
    (TB-BTN submnu (LTF "Password") "CORE.Password.png" "CORE.Password" nil)
	;(TB-BTN submnu (LTF "Translate") "CORE.Translate.png" "CORE.TranslateDB" nil)
    (TB-BTN submnu (LTF "Shortkeys") "CORE.MapShortcuts.png" "CORE.MapShortcuts" nil)
    (TB-BTN submnu "-") ;separator
    (TB-BTN submnu (LTF "Drawing units") "CORE.DrawingUnits.png" "CORE.DrawingUnits" nil)
    (TB-BTN submnu (LTF "Point style") "CAD.PointStyle.png" "CAD.PointStyle" nil)
    (TB-BTN submnu (LTF "Dimension style") "CAD.DimStyle.png" "CAD.DimStyle" nil)

(SETQ submnu (TB-SYSBTN (LTF "Subscription") "CORE.Subscription.png" "CORE.License" nil))
(SETQ submnu (TB-SYSBTN (LTF "About") "CORE.About.png" "CORE.About" nil))
(SETQ submnu (TB-SYSBTN (LTF "Changelog") "CORE.Changelog.png" "CORE.ChangeLog" nil))
(SETQ submnu (TB-SYSBTN (LTF "Check for updates") "CORE.CheckForUpdates.png" "CORE.CheckForUpdates" nil))

(SETQ submnu (TB-SYSBTN (LTF "Exit") "CORE.Exit.png" "CORE.Exit" nil))

;;;;;;;;;;;;;;;;;;;;;;;;;;;;;;;;;;;;;;;;
;          Create toolbar              ;
;;;;;;;;;;;;;;;;;;;;;;;;;;;;;;;;;;;;;;;;
(IF (MODULES 4) ; IF CAM
  (PROGN
    (SETQ tab (TB-TAB (LTF "CAM")))
      (TB-BTN tab (LTF "Select") "Cam2d2.Material.png" "Cam2d2.MacMat2" "0")

	(SETQ grp (TB-GRP tab (LTF "Setup")))
	   (TB-BTN grp (LTF "Machine") "Cam2d2.MachineISF.png" "Cam2d2.MachineISF" nil)
    (TB-BTN tab (LTF "Import") "CAD.Import.png" "CAD.Import" "Ctrl+I")
	(TB-BTN tab (LTF "Create") "Cam2d2.CreatePart.png" "Cam2d2.CreatePart" "1")
	(TB-BTN tab (LTF "Quality") "Cam2d2.Quality.png" "Cam2d2.Quality" nil)
	;(TB-BTN tab (LTF "Tools") "Cam2d2.ToolSetup.png" "Cam2d2.ToolSetup" nil)
	(TB-BTN tab (LTF "Properties") "Cam2d2.PartProperties.png" "Cam2d2.PartProperties" nil)
		(SETQ grp (TB-GRP tab (LTF "Part")))
        	(TB-BTN grp (LTF "TAC-LAG") "Cam2d2.TaperControl.png" "Cam2d2.TaperControl" nil)
          	;(TB-BTN grp (LTF "Properties") "Cam2d2.PartProperties.png" "Cam2d2.PartProperties" nil)
			(TB-BTN grp (LTF "Tools") "Cam2d2.ToolSetup.png" "Cam2d2.ToolSetup" nil)
          	(TB-BTN grp (LTF "Add other objects") "Cam2d2.AddOtherObjects.png" "Cam2d2.AddOtherObjects" nil)
			(TB-BTN grp (LTF "Part text") "Cam2d2.PartText.png" "Cam2d2.PartText" nil)
			(TB-BTN grp (LTF "Inkjet") "Cam2d2.Inkjet.png" "Cam2d2.Inkjet" nil)
			(TB-BTN grp (LTF "Browser") "Cam2d2.PartBrowser.png" "Cam2d2.DockedBrowser" "F2")
			;(TB-BTN grp (LTF "Browser") "Cam2d2.PartBrowser.png" "Cam2d2.PartBrowser" "F2")
			(TB-BTN grp (LTF "Join") "Cam2d2.JoinParts.png" "Cam2d2.JoinParts" nil)
			(TB-BTN grp (LTF "Split") "Cam2d2.SplitParts.png" "Cam2d2.SplitParts" nil)
			(TB-BTN grp (LTF "Stretch") "Cam2d2.StretchPart.png" "Cam2d2.StretchPart" nil)
          	(TB-BTN grp (LTF "Offset") "Cam2d2.OffsetPart.png" "Cam2d2.OffsetPart" nil)
			(TB-BTN grp (LTF "Clone") "Cam2d2.ClonePart.png" "Cam2d2.ClonePart" nil)
          	(TB-BTN grp (LTF "Speed optimisation") "Cam2d2.SpeedRamping.png" "Cam2d2.SpeedRamping" nil)
          	;(TB-BTN grp (LTF "Tube Define (Deprecated)") "TUBE.Tube2.png" "TUBE.Tube2" nil)
	(TB-BTN tab (LTF "Contour") "Cam2d2.ContourCut.png" "Cam2d2.ContourCut" "2")
	(TB-BTN tab (LTF "Quick") "Cam2d2.Quick.png" "Cam2d2.Quick" nil)
	(TB-BTN tab (LTF "Marking") "Cam2d2.Marking.png" "Cam2d2.Marking" nil)
        (IF (NOT (MODULES 9)) (TB-BTN tab (LTF "3D-3X") "Cam2d2.3D5X.png" "Cam2d2.3D5XV2" nil))

	(SETQ grp (TB-GRP tab (LTF "Toolpath")))
          	(TB-BTN grp (LTF "Holes") "Cam2d2.Holes.png" "Cam2d2.Holes" nil)
		(TB-BTN grp (LTF "Manual") "Cam2d2.Manual.png" "Cam2d2.Manual" nil)
    (TB-BTN grp (LTF "Quick bevel (Deprecated)") "Cam2d2.QuickBevel.png" "Cam2d2.QuickBevel" nil)
          	(TB-BTN grp (LTF "Loops") "Cam2d2.MultiLoops.png" "Cam2d2.MultiLoops" nil)
		(TB-BTN grp (LTF "Bridges") "Cam2d2.Bridges.png" "Cam2d2.Bridges" nil)
		(TB-BTN grp (LTF "Common") "Cam2d2.CommonCutlines.png" "Cam2d2.CommonCutlines" nil)
		(TB-BTN grp (LTF "Circle cut") "Cam2d2.CircleCut.png" "Cam2d2.CircleCut" nil)
		(TB-BTN grp (LTF "Cutoff") "Cam2d2.CutOff.png" "Cam2d2.CutOff" nil)
          	(TB-BTN grp (LTF "Gridcut") "Cam2d2.GridCut.png" "Cam2d2.GridCut" nil)
		(TB-BTN grp (LTF "Clone") "Cam2d2.CloneCutting.png" "Cam2d2.CloneCutting" nil)
		(TB-BTN grp (LTF "Break") "Cam2d2.BreakToolpath.png" "Cam2d2.BreakToolpath" nil)
		(TB-BTN grp (LTF "Tool setup") "Cam2d2.ToolpathToolSetup.png" "Cam2d2.ToolpathToolSetup" nil)
	(TB-BTN tab (LTF "Edit") "Cam2d2.EditPart.png" "Cam2d2.EditPart" nil)
	(TB-BTN tab (LTF "Delete") "Cam2d2.RemoveCutting.png" "Cam2d2.RemoveCutting" nil)
	(SETQ grp (TB-GRP tab (LTF "Modify")))
		(TB-BTN grp (LTF "Micro joints") "Cam2d2.MicroJoints.png" "Cam2d2.MicroJoints" nil)
		(TB-BTN grp (LTF "Chain") "Cam2d2.ChainCutting.png" "Cam2d2.ChainCutting" nil)
		(TB-BTN grp (LTF "Disconnect") "Cam2d2.DisconnectToolpath.png" "Cam2d2.DisconnectToolpath" nil)
	      	;(TB-BTN tab (LTF "HeightMap") "CAD.HeightMap.png" "CAD.HeightMap" nil)
        (IF (MODULES 9)
          (PROGN
			(TB-BTN tab (LTF "Bevel2D") "Cam2d2.2DTo3D.png" "Cam2d2.Bevel2D" "5")
            (TB-BTN tab (LTF "Bevel3D") "Cam2d2.2DTo3D.png" "Cam2d2.3D5XBEVEL" "SHIFT+5")
			(TB-BTN tab (LTF "Bevel cut") "Cam2d2.BevelCut.png" "Cam2d2.BevelCut2" "6")
            ;(TB-BTN tab (LTF "Bevel") "Cam2d2.2DTo3D.png" "Cam2d2.3D5XBEVEL" nil)
			;(TB-BTN tab (LTF "Bevel cut") "Cam2d2.BevelCut.png" "Cam2d2.BevelCut2" nil)
            (TB-BTN tab (STRCAT (LTF "3D-5X")) "Cam2d2.3D5X.png" "Cam2d2.3D5XV2" "F7")

            (TB-BTN tab (LTF "Ruled") "Cam2d2.RuledBevel.png" "Cam2d2.RuledBevel3d5x" nil)
            (SETQ grp (TB-GRP tab (LTF "3D-5X")))
				(TB-BTN grp (LTF "Tilt Cutoff") "Cam2d2.TiltCutoff.png" "Cam2d2.TiltCutoff" nil)
              	(TB-BTN grp (LTF "Uniform") "Cam2d2.RuledBevelUniform3d5x.png" "Cam2d2.RuledBevelUniform3d5x" nil)
            	(TB-BTN grp (LTF "Define (Deprecated)") "Cam2d2.DefineBevel.png" "Cam2d2.DefineBevel" "5")
				(TB-BTN grp (LTF "Ruled bevel (Deprecated)") "Cam2d2.RuledBevel.png" "Cam2d2.RuledBevel" nil)				
	        (TB-BTN grp (LTF "Cut (Deprecated)") "Cam2d2.BevelCut.png" "Cam2d2.BevelCut2" "6")
			)
		)

	(TB-BTN tab (LTF "FastForward") "Cam2d2.FastForward.png" "Cam2d2.FastForward" nil)
    (TB-BTN tab (LTF "Order") "Cam2d2.CutOrder.png" "Cam2d2.CutOrder" "3")
	(TB-BTN tab (LTF "Create CNC") "Cam2d2.Process.png" "Cam2d2.Process2" "4")
	(tb-btn tab (ltf "Delete Cut Orders") (strcat (GETVAR "PATHSCRIPT") "Images/DeleteCutOrders.png") "DeleteCutOrders.lsp" "Shift+3")

	(SETQ grp (TB-GRP tab (LTF "Process")))
		(TB-BTN grp (LTF "Cutting parameters") "Cam2d2.CuttingParameters.png" "Cam2d2.CuttingParameters" nil)
		(TB-BTN grp (LTF "Strategy") "Cam2d2.Strategy.png" "Cam2d2.MachineMethod" nil)
		(TB-BTN grp (LTF "Cost estimate") "Cam2d2.CostEstimate.png" "Cam2d2.CostEstimate" nil)))
		(TB-BTN grp (LTF "Create") "Cam2d2.CreateSheet.png" "Cam2d2.CreateSheet" nil)
		(TB-BTN grp (LTF "Rectangle") "Cam2d2.CreateRectangularSheet.png" "Cam2d2.CreateRectangularSheet" "SHIFT+N")


    (TB-BTN tab (LTF "Create") "Cam2d2.CreateSheet.png" "Cam2d2.CreateSheet" nil)
    (TB-BTN tab (LTF "Rectangle") "Cam2d2.CreateRectangularSheet.png" "Cam2d2.CreateRectangularSheet" "SHIFT+N")
	(tb-btn tab (ltf "Center Parts") (strcat (GETVAR "PATHSCRIPT") "Images/CenterPartsOnSheet.png") "CenterPartsOnSheet.lsp" nil)
	(tb-btn tab (ltf "Delete Parts") (strcat (GETVAR "PATHSCRIPT") "Images/DeletePartsOnSheet.png") "DeletePartsOnSheet.lsp" nil)
    (TB-BTN tab (LTF "Register") "Cam2d2.RegisterSheet.png" "Cam2d2.RegisterSheetDB" nil)
	(TB-BTN tab (LTF "Sheets") "Cam2d2.SheetDatabase.png" "Cam2d2.SheetDB" nil)
	(SETQ grp (TB-GRP tab (LTF "Sheet")))
		(TB-BTN grp (LTF "Lock") "Cam2d2.LockSheet.png" "Cam2d2.LockSheet" nil)
		(TB-BTN grp (LTF "Unlock") "Cam2d2.UnlockSheet.png" "Cam2d2.UnlockSheet" nil)
		;(SETQ submnu (TB-BTN grp (LTF "Export") "Cam2d2.OpenSheetAdd.png" "Cam2d2.OpenSheetAdd" nil))
        		;(TB-BTN submnu (LTF "Export sheet to scrap") "Cam2d2.OpenSheetAdd.png" "Cam2d2.OpenRestSheetAdd" nil)
          	;(SETQ submnu (TB-BTN grp (LTF "Open") "Cam2d2.OpenSheet.png" "Cam2d2.OpenSheet" nil))
        		;(TB-BTN submnu (LTF "Open scrap sheets") "Cam2d2.OpenSheet.png" "Cam2d2.OpenRestSheet" nil)
		(TB-BTN grp (LTF "Divide") "Cam2d2.DivideSheet.png" "Cam2d2.DivideSheet" nil)
		(TB-BTN grp (LTF "From hole") "Cam2d2.SubSheet.png" "Cam2d2.SubSheet" nil)
          	(SETQ submnu (TB-BTN grp (LTF "Inventory") "Cam2d2.SheetInventory.png" "Cam2d2.SheetInventory" nil))
          		;(TB-BTN submnu (LTF "All materials") "Cam2d2.SheetInventory.png" "Cam2d2.SheetReport" nil)

		(TB-BTN grp (LTF "History") "Cam2d2.History.png" "Cam2d2.History" nil)
		;(TB-BTN grp (LTF "Import from R7-R9") "Cam2d2.ImportSheet.png" "Cam2d2.ImportSheet" nil)
    (IF (MODULES 10)
      (PROGN
      	(TB-BTN tab (LTF "Register") "ORGANIZER.Register.png" "ORGANIZER.Register" nil)
	      (TB-BTN tab (LTF "Organizer") "ORGANIZER.Organizer.png" "ORGANIZER.Organizer" nil)
	      (SETQ grp (TB-GRP tab (LTF "Organizer")))
		)
	)



;;;;;;;;;;;;;;;;;;;;;;;;;;;;;;;;;;;;;;;;
;          Create toolbar              ;
;;;;;;;;;;;;;;;;;;;;;;;;;;;;;;;;;;;;;;;;
(SETQ tab (TB-TAB (LTF "CAD")))
	(TB-BTN tab (LTF "Undo") "CORE.Undo.png" "CORE.Undo" "Ctrl+Z")
	(TB-BTN tab (LTF "Redo") "CORE.Redo.png" "CORE.Redo" "Ctrl+Y")
	(SETQ grp (TB-GRP tab (LTF "System")))
		(TB-BTN grp (LTF "Purge") "CORE.Purge.png" "CORE.Purge" nil)
		(TB-BTN grp (LTF "Status") "CORE.Status.png" "CORE.Status" nil)
		;(TB-BTN grp (LTF "User data folder") "CORE.UserDataFolder.png" "CORE.UserDataFolder" nil)
		(TB-BTN grp (LTF "Shared folder") "CORE.SharedFolder.png" "CORE.SharedFolder" nil)
		(TB-BTN grp (LTF "Service center") "CORE.ServiceCenter.png" "CORE.ServiceCenter" nil)
		(SETQ submnu (TB-BTN grp  (LTF "Support") "Cam2d2.BugReport.png" "Cam2d2.BugReport" nil))
      (TB-BTN submnu (LTF "Reset") "Cam2d2.Reset.png" "Cam2d2.BugReportRestore" nil)

	(TB-BTN tab (LTF "Line") "CAD.Line.png" "CAD.Line" "L")
    (TB-BTN tab (LTF "Circle") "CAD.Circle.png" "CAD.Circle" "C")
	(TB-BTN tab (LTF "Rectangle") "CAD.Rectangle.png" "CAD.Rectangle" "N")
	(SETQ grp (TB-GRP tab (LTF "Draw")))
		(TB-BTN grp (LTF "Point") "CAD.Point.png" "CAD.Point" "Shift+P")
		(SETQ submnu (TB-BTN grp (LTF "Arc") "CAD.Arc.png" "CAD.Arc" "A"))
			(TB-BTN submnu (LTF "Start, on, end") "CAD.Arc.png" "CAD.Arc" "A")
			(TB-BTN submnu (LTF "Center, start, end") "CAD.ArcCSE.png" "CAD.ArcCSE" nil)
			(TB-BTN submnu (LTF "Start, center, angle") "CAD.ArcSCA.png" "CAD.ArcSCA" nil)
			(TB-BTN submnu (LTF "Start, center, length") "CAD.ArcSCL.png" "CAD.ArcSCL" nil)
			(TB-BTN submnu (LTF "Start, end, angle") "CAD.ArcSEA.png" "CAD.ArcSEA" nil)
			(TB-BTN submnu (LTF "Start, end, direction") "CAD.ArcSED.png" "CAD.ArcSED" nil)
			(TB-BTN submnu (LTF "Start, end, radius") "CAD.ArcSER.png" "CAD.ArcSER" nil)
		(SETQ submnu (TB-BTN grp (LTF "Circle") "CAD.Circle.png" "CAD.Circle" "C"))
			(TB-BTN submnu (LTF "From center and 1 point") "CAD.Circle.png" "CAD.Circle" "C")
			(TB-BTN submnu (LTF "From 2 points") "CAD.Circle2P.png" "CAD.Circle2P" nil)
			(TB-BTN submnu (LTF "From 2 points and radius") "CAD.Circle2PR.png" "CAD.Circle2PR" nil)
			(TB-BTN submnu (LTF "From 3 points") "CAD.Circle3P.png" "CAD.Circle3P" nil)
			(TB-BTN submnu (LTF "Enclosing") "CAD.EnclosingCircle.png" "CAD.EnclosingCircle" nil)
		(SETQ submnu (TB-BTN grp (LTF "Rectangle") "CAD.Rectangle.png" "CAD.Rectangle" "N"))
			(TB-BTN submnu (LTF "Rectangle") "CAD.Rectangle.png" "CAD.Rectangle" "N")
			(TB-BTN submnu (LTF "Rectangle XYC") "CAD.RectangleXYC.png" "CAD.RectangleXYC" nil)
			(TB-BTN submnu (LTF "Bounding box") "CAD.RectangleBB.png" "CAD.RectangleBB" nil)
		(TB-BTN grp (LTF "Polyline") "CAD.Polyline.png" "CAD.Polyline" "P")
		(TB-BTN grp (LTF "Sketch") "CAD.Sketch.png" "CAD.Sketch" nil)
		(TB-BTN grp (LTF "Spline") "CAD.Spline.png" "CAD.Spline" nil)
		(TB-BTN grp (LTF "Ellipse") "CAD.Ellipse.png" "CAD.Ellipse" "Shift+E")
		(TB-BTN grp (LTF "Solid") "CAD.Solid.png" "CAD.Solid" nil)
		(TB-BTN grp (LTF "Hatch") "CAD.Hatch.png" "CAD.Hatch" nil)
	(TB-BTN tab (LTF "Parametric") "PARAMPART.ParametricShapes.png" "PARAMPART.ParametricShapes" nil)
	(TB-BTN tab (LTF "N-gon") "CAD.NGon.png" "CAD.NGon" nil)
	(SETQ grp (TB-GRP tab (LTF "Shape")))
		(TB-BTN grp (LTF "Obround") "CAD.Obround.png" "CAD.Obround" nil)
		(TB-BTN grp (LTF "Swell") "CAD.Swell.png" "CAD.Swell" nil)
        (TB-BTN grp (LTF "Unswell") "CAD.Unswell.png" "CAD.Unswell" nil)
		(TB-BTN grp (LTF "Puzzle") "CAD.Puzzle.png" "CAD.Puzzle" nil)
		(TB-BTN grp (LTF "Boundary poly") "CAD.BPoly.png" "CAD.BPoly" nil)
	;(TB-BTN tab (LTF "Offset") "CAD.Offset.png" "CAD.Offset" "O")
	(TB-BTN tab (LTF "Fillet") "CAD.Fillet.png" "CAD.Fillet" "F")
	(TB-BTN tab (LTF "Zero fillet") "CAD.ZeroFillet.png" "CAD.ZeroFillet" "Shift+F")
	(TB-BTN tab (LTF "Trim") "CAD.Trim.png" "CAD.Trim" "T")
	(TB-BTN tab (LTF "Extend") "CAD.Extend.png" "CAD.Extend" nil)
	(SETQ grp (TB-GRP tab (LTF "Modify")))
		;(TB-BTN grp (LTF "Zero fillet") "CAD.ZeroFillet.png" "CAD.ZeroFillet" "Shift+F")
		(TB-BTN grp (LTF "Offset") "CAD.Offset.png" "CAD.Offset" "O")
		(TB-BTN grp (LTF "Chamfer") "CAD.Chamfer.png" "CAD.Chamfer" nil)
		(TB-BTN grp (LTF "Smooth connect") "CAD.SmoothConnect.png" "CAD.SmoothConnect" nil)
		(TB-BTN grp (LTF "Lengthen") "CAD.Lengthen.png" "CAD.Lengthen" nil)
		;(TB-BTN grp (LTF "Extend") "CAD.Extend.png" "CAD.Extend" nil)
		(TB-BTN grp (LTF "Boolean") "CAD.Boolean.png" "CAD.Boolean" "B")
		(TB-BTN grp (LTF "Polyline editor") "CAD.PolylineEditor.png" "CAD.PolylineEditor" nil)
		(TB-BTN grp (LTF "Break") "CAD.Break.png" "CAD.Break" nil)
		(TB-BTN grp (LTF "Delete") "CAD.Erase.png" "CAD.Erase" "E")
	(TB-BTN tab (LTF "Join") "CAD.Join.png" "CAD.Join" "J")
	(TB-BTN tab (LTF "Layer") "CORE.Layer.png" "CORE.Layer" "Y")
	(TB-BTN tab (LTF "Explode") "CAD.Explode.png" "CAD.Explode" "X")
	(SETQ grp (TB-GRP tab (LTF "Group")))
		(TB-BTN grp (LTF "Define attributes") "CAD.AttDef.png" "CAD.AttDef" nil)
		(TB-BTN grp (LTF "Create block") "CORE.Block.png" "CORE.Block" "Ctrl+B")
		(TB-BTN grp (LTF "Insert block") "CORE.Insert.png" "CORE.Insert" nil)
		(TB-BTN grp (LTF "Group") "CAD.Group.png" "CAD.Group" "G")
		(TB-BTN grp (LTF "Save block") "CORE.WriteBlock.png" "CORE.WriteBlock" nil)
	;(TB-BTN tab (LTF "Move") "CAD.Move.png" "CAD.Move" "M")
	;(TB-BTN tab (LTF "Rotate") "CAD.Rotate.png" "CAD.Rotate" "R")
	;(TB-BTN tab (LTF "Copy") "CAD.MultiCopy.png" "CAD.MultiCopy" "Shift+C")
	(TB-BTN tab (LTF "Array") "CAD.Array.png" "CAD.Array" nil)
	(TB-BTN tab (LTF "Quick move") "CAD.SuperMove.png" "CAD.SuperMove" "Ctrl+M")
	(TB-BTN tab (LTF "Stretch") "CAD.Stretch.png" "CAD.Stretch" nil)
	(SETQ grp (TB-GRP tab (LTF "Transform")))
		(TB-BTN grp (LTF "Mirror") "CAD.Mirror.png" "CAD.Mirror" "Shift+M")
		(TB-BTN grp (LTF "Scale") "CAD.Scale.png" "CAD.Scale" "S")
		(TB-BTN grp (LTF "Reference scale") "CAD.Scale.png" "CAD.QuickScale" nil)
		(tb-btn grp (ltf "ResizeRectangle") (strcat (GETVAR "PATHSCRIPT") "Images/ResizeRectangle.png") "ResizeRectangle.lsp" nil)
		(TB-BTN grp (LTF "Project") "CAD.Project.png" "CAD.Projection" nil)
		;(TB-BTN grp (LTF "Quick move") "CAD.SuperMove.png" "CAD.SuperMove" "Ctrl+M")
		;(TB-BTN grp (LTF "Stretch") "CAD.Stretch.png" "CAD.Stretch" nil)
		(TB-BTN grp (LTF "Skew") "CAD.Skew.png" "CAD.Skew" nil)
		;(TB-BTN grp (LTF "Array") "CAD.Array.png" "CAD.Array" nil)
		(TB-BTN grp (LTF "Move") "CAD.Move.png" "CAD.Move" "M")
		(TB-BTN grp (LTF "Rotate") "CAD.Rotate.png" "CAD.Rotate" "R")
		(TB-BTN grp (LTF "Copy") "CAD.MultiCopy.png" "CAD.MultiCopy" "Shift+C")
	(TB-BTN tab (LTF "Dimension") "CAD.Dimension.png" "CAD.Dimension" "D")

	(TB-BTN tab (LTF "Text") "CAD.Text.png" "CAD.Text" "Shift+T")
	(SETQ grp (TB-GRP tab (LTF "Dimension")))
		;(TB-BTN grp (LTF "Rotated dimension") "CAD.RotatedDimension.png" "CAD.RotatedDimension" nil)
    (TB-BTN grp (LTF "Linear") "CAD.LinearDimension.png" "CAD.LinearDimension" nil)
    (TB-BTN grp (LTF "Diameter") "CAD.DiameterDimension.png" "CAD.DiameterDimension" nil)
		(TB-BTN grp (LTF "Radius") "CAD.RadiusDimension.png" "CAD.RadiusDimension" nil)
		(TB-BTN grp (LTF "Positions") "CAD.DimPos.png" "CAD.DimPos" nil)
    (TB-BTN grp (LTF "Angular dimension") "CAD.AngularDimension.png" "CAD.AngularDimension" nil)
		(TB-BTN grp (LTF "Leader") "CAD.Leader.png" "CAD.Leader" nil)
		(TB-BTN grp (LTF "Dimension style") "CAD.DimStyle.png" "CAD.DimStyle" "Shift+D")
	(TB-BTN tab (LTF "Extents") "CORE.ZoomExtents.png" "CORE.ZoomExtents" "Ctrl+Shift+E")
	(SETQ grp (TB-GRP tab (LTF "View")))
		(TB-BTN grp (LTF "Pan") "CORE.Pan.png" "CORE.Pan" "Ctrl+Shift+P")
		(TB-BTN grp (LTF "Zoom") "CORE.Zoom.png" "CORE.Zoom" nil)
		(TB-BTN grp (LTF "Zoom window") "CORE.ZoomWindow.png" "CORE.ZoomWindow" nil)
		(TB-BTN grp (LTF "Zoom object") "CORE.ZoomPart.png" "CORE.ZoomObject" nil)
		(TB-BTN grp (LTF "Color") "CORE.Color.png" "CORE.Color" nil)
		(TB-BTN grp (LTF "Line type") "CORE.LineType.png" "CORE.LineType" nil)
		(TB-BTN grp (LTF "Line weight") "CORE.LineWeight.png" "CORE.LineWeight" nil)
		(TB-BTN grp (LTF "Send to back") "CORE.SendToBack.png" "CORE.SendToBack" nil)
		(TB-BTN grp (LTF "Bring to front") "CORE.BringToFront.png" "CORE.BringToFront" nil)
	(TB-BTN tab (LTF "Info") "CORE.Info.png" "CORE.Info" "I")
	(TB-BTN tab (LTF "Distance") "CAD.Distance.png" "CAD.Distance" "Ctrl+D")
	(SETQ grp (TB-GRP tab (LTF "Info")))
		(TB-BTN grp (LTF "Id") "CORE.Id.png" "CORE.Id" nil)

(IF (OR (MODULES 1) (MODULES 2) (MODULES 3) (MODULES 8) (MODULES 13)) ; Data eXhange, Tools, SignMaker,TilMaker
	(PROGN
		(IF (MODULES 2) ; If tools
			(PROGN
				(SETQ tab (TB-TAB (LTF "TOOLS")))
					(TB-BTN tab (LTF "Analyze") "CAMTools.ContourAnalyzer.png" "CAMTools.ContourAnalyzer" "Shift+A")
					(TB-BTN tab (LTF "Clean up") "CAMTools.CleanUp.png" "CAMTools.CleanUp" "Shift+Q")
					(TB-BTN tab (LTF "EdgeFix") "CAMTools.EdgeFix.png" "CAMTools.EdgeFix" nil)
					(TB-BTN tab (LTF "Curvefit") "CAMTools.Curvefit.png" "CAMTools.Curvefit" nil)
					(TB-BTN tab (LTF "Boundary scan") "CAMTools.BoundaryScan.png" "CAMTools.BoundaryScan" nil)
					(TB-BTN tab (LTF "Replace") "CAMTools.ObjectReplace.png" "CAMTools.ObjectReplace" nil)
					(TB-BTN tab (LTF "Poly joint") "CAMTools.PolyJoint.png" "CAMTools.PolyJoint" nil)
					(SETQ grp (TB-GRP tab (LTF "CAM tools")))
						(TB-BTN grp (LTF "Boundary trim") "CAMTools.BoundaryTrim.png" "CAMTools.BoundaryTrim" nil)
						(TB-BTN grp (LTF "Corner cutout") "CAMTools.CornerCutout.png" "CAMTools.CornerCutout" nil)
						(TB-BTN grp (LTF "Vectorize") "CAMTools.Vectorize.png" "CAMTools.Vectorize" nil)
						(TB-BTN grp (LTF "Divide") "CAMTools.Divide.png" "CAMTools.Divide" nil)
						(TB-BTN grp (LTF "Pocketing") "CAD.Pocketing.png" "CAD.Pocketing" nil)
						(TB-BTN grp (LTF "Convex hull") "CAMTools.ConvexHull.png" "CAMTools.ConvexHull" nil)
						(TB-BTN grp (LTF "Align") "CAMTools.Align.png" "CAMTools.Align" nil)
						(TB-BTN grp (LTF "Dovetail") "CAMTools.Dovetail.png" "CAMTools.Dovetail" nil)
			)
		)
		(IF (MODULES 3)
			(PROGN
				(TB-BTN tab (LTF "Type") "SignMaker.FontTracer.png" "SignMaker.FontTracer" nil)
				(TB-BTN tab (LTF "Image") "CAD.Image.png" "CAD.Image" nil)
				(TB-BTN tab (LTF "Trace") "ImageTracer.Trace.png" "ImageTracer.Trace" nil)
				(SETQ grp (TB-GRP tab (LTF "Sign maker")))
					(TB-BTN grp (LTF "Optimize") "CAD.Optimise.png" "CAD.RescaleImage" nil)
			)
		)
		(IF (MODULES 8)
			(PROGN
				  (TB-BTN tab (LTF "Tile") "SignMaker.TileMaker.png" "SignMaker.TileMaker" nil)
				  (TB-BTN tab (LTF "Cut") "NEST.TileCut.png" "NEST.TileCut" nil)
				  (TB-BTN tab (LTF "Inlay") "NEST.Inlay.png" "NEST.Inlay" nil)
				  (SETQ grp (TB-GRP tab (LTF "Tile maker")))
			)
		)
		(IF (MODULES 1)
			(PROGN
				  (TB-BTN tab (LTF "NC reader") "DataExchange.NCReader.png" "DataExchange.NCReader" nil)
				  (SETQ grp (TB-GRP tab (LTF "Data ex")))
			)
		)
		(IF (MODULES 13)
			(PROGN
				(TB-BTN tab (LTF "Insert") "Cam2d2.CameraSnapshot.png" "Cam2d2.CameraSnapshot" nil)
				(SETQ grp (TB-GRP tab (LTF "Camera")))
					(TB-BTN grp (LTF "Config") "Cam2d2.CameraCalibration.png" "Cam2d2.CameraCalibration" nil)
			)
		)
	)
)

(IF (MODULES 6)
	(PROGN
    (SETQ tab (TB-TAB (LTF "NEST")))
      (TB-BTN tab (LTF "Select") "Cam2d2.Material.png" "Cam2d2.MacMat2" "0")
	(SETQ grp (TB-GRP tab (LTF "Setup")))
      		(TB-BTN tab (LTF "Create") "Cam2d2.CreateSheet.png" "Cam2d2.CreateSheet" nil)
        	(TB-BTN tab (LTF "Rectangle") "Cam2d2.CreateRectangularSheet.png" "Cam2d2.CreateRectangularSheet" "SHIFT+N")
			(TB-BTN tab (LTF "Register") "Cam2d2.RegisterSheet.png" "Cam2d2.RegisterSheetDB" nil)
			(TB-BTN tab (LTF "Sheets") "Cam2d2.SheetDatabase.png" "Cam2d2.SheetDB" nil)
		(SETQ grp (TB-GRP tab (LTF "Sheet")))
				(TB-BTN grp (LTF "Lock") "Cam2d2.LockSheet.png" "Cam2d2.LockSheet" nil)
				(TB-BTN grp (LTF "Unlock") "Cam2d2.UnlockSheet.png" "Cam2d2.UnlockSheet" nil)
				;(SETQ submnu (TB-BTN grp (LTF "Export") "Cam2d2.OpenSheetAdd.png" "Cam2d2.OpenSheetAdd" nil))
					;(TB-BTN submnu (LTF "Export sheet to scrap") "Cam2d2.OpenSheetAdd.png" "Cam2d2.OpenRestSheetAdd" nil)
				;(SETQ submnu (TB-BTN grp (LTF "Open") "Cam2d2.OpenSheet.png" "Cam2d2.OpenSheet" nil))
        		;(TB-BTN submnu (LTF "Open scrap sheets") "Cam2d2.OpenSheet.png" "Cam2d2.OpenRestSheet" nil)
				(TB-BTN grp (LTF "Divide") "Cam2d2.DivideSheet.png" "Cam2d2.DivideSheet" nil)

          		;(TB-BTN submnu (LTF "All materials") "Cam2d2.SheetInventory.png" "Cam2d2.SheetReport" nil)
				(TB-BTN grp (LTF "From hole") "Cam2d2.SubSheet.png" "Cam2d2.SubSheet" nil)
          	(SETQ submnu (TB-BTN grp (LTF "Inventory") "Cam2d2.SheetInventory.png" "Cam2d2.SheetInventory" nil))
				(TB-BTN grp (LTF "History") "Cam2d2.History.png" "Cam2d2.History" nil)
				;(TB-BTN grp (LTF "Import from R7-R9") "Cam2d2.ImportSheet.png" "Cam2d2.ImportSheet" nil)
				(TB-BTN tab (LTF "Create") "Cam2d2.CreatePart.png" "Cam2d2.CreatePart" "1")
		(TB-BTN tab (LTF "Browser") "Cam2d2.PartBrowser.png" "Cam2d2.PartBrowser" "F2")
				(TB-BTN tab (LTF "Center parts") "Cam2d2.CenterParts.png" "Cam2d2.CenterHoles" nil)
		(SETQ grp (TB-GRP tab (LTF "Part")))
        	(TB-BTN grp (LTF "TAC-LAG") "Cam2d2.TaperControl.png" "Cam2d2.TaperControl" nil)
          	(TB-BTN grp (LTF "Properties") "Cam2d2.PartProperties.png" "Cam2d2.PartProperties" nil)
			(TB-BTN grp (LTF "Part text") "Cam2d2.PartText.png" "Cam2d2.PartText" nil)
			(TB-BTN grp (LTF "Inkjet") "Cam2d2.Inkjet.png" "Cam2d2.Inkjet" nil)
			(TB-BTN grp (LTF "Browser") "Cam2d2.PartBrowser.png" "Cam2d2.DockedBrowser" "F2")
			(TB-BTN grp (LTF "Join") "Cam2d2.JoinParts.png" "Cam2d2.JoinParts" nil)
			(TB-BTN grp (LTF "Split") "Cam2d2.SplitParts.png" "Cam2d2.SplitParts" nil)
			(TB-BTN grp (LTF "Stretch") "Cam2d2.StretchPart.png" "Cam2d2.StretchPart" nil)
          	(TB-BTN grp (LTF "Offset") "Cam2d2.OffsetPart.png" "Cam2d2.OffsetPart" nil)
			(TB-BTN grp (LTF "Clone") "Cam2d2.ClonePart.png" "Cam2d2.ClonePart" nil)
          	(TB-BTN grp (LTF "Speed optimisation") "Cam2d2.SpeedRamping.png" "Cam2d2.SpeedRamping" nil)
	;(SETQ grp (TB-GRP tab (LTF "Part")))
	    (TB-BTN tab (LTF "Quick") "NEST.BumpNest.png" "NEST.BumpNest" "Q")
	    (TB-BTN tab (LTF "Glide") "NEST.BumpNestGlide.png" "NEST.BumpNestGlide" nil)
	    (TB-BTN tab (LTF "Single") "NEST.SingleNest.png" "NEST.SingleNest" nil)
	    (TB-BTN tab (LTF "Rectangle") "NEST.Rectangle.png" "NEST.Rectangle" nil)
	    (TB-BTN tab (LTF "Circle") "NEST.Circle.png" "NEST.Circle" nil)
      (TB-BTN tab (LTF "Report") "NEST.Report.png" "NEST.Report" nil)
      (SETQ grp (TB-GRP tab (LTF "Nest Level 1")))
      (IF (MODULES 7)
        (PROGN
	        (TB-BTN tab (LTF "Auto") "NEST.AutoNest.png" "NEST.AutoNest" nil)
          (TB-BTN tab (LTF "Re-nest") "NEST.ReNest.png" "NEST.RenestSheet" nil)
          (SETQ grp (TB-GRP tab (LTF "Nest Level 2")))
          (TB-BTN grp (LTF "Auto (Deprecated)") "NEST.AutoNest.png" "NEST.AutoNestOld" nil)))
	)
)


;WARDJET TOOLBAR
(setq trainingPath (strcat (getvar "PATHSHARED") "App/Training/"))
(SETQ tab (TB-TAB (LTF "WARDJET")))
	(tb-btn tab (ltf "") (strcat trainingPath "Images/JeffsIGEMSPage.png") (strcat trainingPath "Jeff's IGEMS Page.lsp") nil)
	(SETQ grp (TB-GRP tab (LTF "YouTube")))
	(tb-btn tab (ltf "Basics") (strcat trainingPath "Images/BasicsWebinar32x25.png") (strcat trainingPath "Basicswebinar.lsp") nil)
	(tb-btn tab (ltf "Adv. Topics") (strcat trainingPath "Images/AdvWebinar32x25.png") (strcat trainingPath "AdvancedTopicswebinar.lsp") nil)
	(tb-btn tab (ltf "APEX60") (strcat (GETVAR "PATHSCRIPT") "Images/APEX60 32x36.png") (strcat trainingPath "APEX60Programming.lsp") nil)
	(tb-btn tab (ltf "Common Line Cutting") "Cam2d2.CommonCutLines.png" (strcat trainingPath "CommonLineCutting.lsp") nil)
	(tb-btn tab (ltf "Nesting") "Nest.AutoNest.png" (strcat trainingPath "NestingWebinar.lsp") nil)
	(tb-btn tab (ltf "3D-5X") "CORE.3D5XSamples.png" (strcat trainingPath "3D_5XWebinar.lsp") nil)

	(SETQ grp (TB-GRP tab (LTF "Training Videos")))
		(SETQ submenuapex (TB-BTN grp (LTF "APEX 60") (strcat (GETVAR "PATHSCRIPT") "Images/APEX60 32x36.png") "" nil))
			(TB-BTN submenuapex (LTF "Taper Angle Control") (strcat (GETVAR "PATHSCRIPT") "Images/APEX60 32x36.png") (strcat trainingPath "TAC.lsp") nil)
			(tb-btn submenuapex (ltf "APEX 60 Calibration (MOVE)") (strcat (GETVAR "PATHSCRIPT") "Images/APEX60 32x36.png") (strcat trainingPath "APEX60CalibrationMOVE.lsp") nil)
			(tb-btn submenuapex (ltf "APEX 60 Calibration (Ikuhlu)") (strcat (GETVAR "PATHSCRIPT") "Images/APEX60 32x36.png") (strcat trainingPath "APEX60CalibrationIkuhlu.lsp") nil)

		(SETQ submenu (TB-BTN grp (LTF "CAD") (strcat trainingPath "Images/CAD.png") "" nil))
			(tb-btn submenu (ltf "Snaps, Grips, Ortho, Shortcut Keys")(strcat trainingPath "Images/Snaps.png") (strcat trainingPath "CADSnaps.lsp") nil)
			(tb-btn submenu (ltf "Scale") "CAD.Scale.png" (strcat trainingPath "CADScale.lsp") nil)
			(tb-btn submenu (ltf "Scale by Reference") "CAD.Scale.png" (strcat trainingPath "CADScalebyReference.lsp") nil)
			(tb-btn submenu (ltf "Reference Scale") "CAD.Scale.png" (strcat trainingPath "CADReferenceScale.lsp") nil)
			(tb-btn submenu (ltf "Rotate Reference") "CAD.Rotate.png" (strcat trainingPath "CADRotateReference.lsp") nil)
			(tb-btn submenu (ltf "Stretch") "CAD.Stretch.png" (strcat trainingPath "Stretch.lsp") nil)

		(SETQ submenuCAM (TB-BTN grp (LTF "CAM") (strcat trainingPath "Images/CAM.png") "" nil))
			(SETQ submenuPart (TB-BTN submenuCAM (LTF "Part") (strcat trainingPath "") "" nil))
				(tb-btn submenuPart (ltf "Import DXF") "CAD.Import.png" (strcat trainingPath "ImportDXF.lsp") nil)
				(tb-btn submenuPart (ltf "Import PDF") (strcat trainingPath "Images/ImportPDF.png") (strcat trainingPath "ImportPDF.lsp") nil)
				(tb-btn submenuPart (ltf "Create") "Cam2d2.CreatePart.png" (strcat trainingPath "CreatePart.lsp") nil)
				(tb-btn submenuPart (ltf "Quality") "Cam2d2.Quality.png" (strcat trainingPath "Quality.lsp") nil)
				(tb-btn submenuPart (ltf "Tools") "Cam2d2.ToolSetup.png" (strcat trainingPath "Tools.lsp") nil)
				(tb-btn submenuPart (ltf "Add Other Objects") "cam2d2.AddOtherObjects.png" (strcat trainingPath "AddOtherObjects.lsp") nil)
				(tb-btn submenuPart (ltf "Join") "Cam2d2.JoinParts.png" (strcat trainingPath "JoinParts.lsp") nil)
				(tb-btn submenuPart (ltf "Stretch") "Cam2d2.StretchPart.png" (strcat trainingPath "Stretch.lsp") nil)
				(tb-btn submenuPart (ltf "Clone Part") "Cam2d2.ClonePart.png" (strcat trainingPath "ClonePart.lsp") nil)

			(SETQ submenutoolpath (TB-BTN submenuCAM (LTF "Toolpath") (strcat trainingPath "") "" nil))
			(SETQ submenuquick (TB-BTN submenutoolpath (LTF "Quick") "Cam2d2.Quick.png" "" nil))
				(tb-btn submenuquick (ltf "Quick - Contour") (strcat trainingPath "Images/QuickContour.png") (strcat trainingPath "CAMQuickContour.lsp") nil)
				(tb-btn submenuquick (ltf "Quick - Slit") (strcat trainingPath "Images/QuickSlit.png") (strcat trainingPath "CAMQuickSlitCuts.lsp") nil)
			(tb-btn submenutoolpath (ltf "Marking") "Cam2d2.Marking.png" (strcat trainingPath "CAMMarking.lsp") nil)
				(tb-btn submenutoolpath (ltf "How to Pierce a Point") "Cam2d2.Holes.png" (strcat trainingPath "HowToPierceaPoint.lsp") nil)
				(tb-btn submenutoolpath (ltf "Manual") "Cam2d2.Manual.png" (strcat trainingPath "Manual.lsp") nil)
				(tb-btn submenutoolpath (ltf "Bridges \&& Chain Cutting") "Cam2d2.Bridges.png" (strcat trainingPath "CAMBridgesandChainCutting.lsp") nil)
				(tb-btn submenutoolpath (ltf "Cutoff") "Cam2d2.Cutoff.png" (strcat trainingPath "Cutoff.lsp") nil)
				(tb-btn submenutoolpath (ltf "Clone Toolpath") "Cam2d2.CloneCutting.png" (strcat trainingPath "CloneCutting.lsp") nil)
				(tb-btn submenutoolpath (ltf "Break") "Cam2d2.BreakToolpath.png" (strcat trainingPath "BreakToolpath.lsp") nil)
				(TB-BTN submenutoolpath (LTF "Tool setup") "Cam2d2.ToolpathToolSetup.png" (strcat trainingPath "ToolpathToolSetup.lsp") nil)
				
			(SETQ submenuModify (TB-BTN submenuCAM (LTF "Modify") (strcat trainingPath "") "" nil))
				(tb-btn submenuModify (ltf "Micro Joints (or tabs)") "Cam2d2.MicroJoints.png" (strcat trainingPath "MicroJoints.lsp") nil)
				(tb-btn submenuModify (ltf "Bridges \&& Chain Cutting") "Cam2d2.ChainCutting.png" (strcat trainingPath "CAMBridgesandChainCutting.lsp") nil)
				(tb-btn submenuModify (ltf "Disconnect") "Cam2d2.DisconnectToolpath.png" (strcat trainingPath "DisconnectToolpath.lsp") nil)

			(SETQ submenureports (TB-BTN submenuCAM (LTF "Reports") "Nest.Report.png" "" nil))
				(tb-btn submenureports (ltf "Customize Reports") "Nest.Report.png" (strcat trainingPath "CustomizeReports.lsp") nil)
				(tb-btn submenureports (ltf "Material Cost") (strcat trainingPath "Images/CostEstimate.png") (strcat trainingPath "MaterialCost.lsp") nil)
				(tb-btn submenureports (ltf "Colored Parts") (strcat trainingPath "Images/ColoredParts.png") (strcat trainingPath "ColoredPartsonReport.lsp") nil)
				(tb-btn submenureports (ltf "Layout Mode") (strcat trainingPath "Images/LayoutMode.png") (strcat trainingPath "LayoutMode.lsp") nil)

		(SETQ submenuTools (TB-BTN grp (LTF "Tools") "Cam2d2.MacMat2.png" "" nil))
				(tb-btn submenuTools (ltf "Analyze \&& Clean up") "CAMTools.ContourAnalyzer.png" (strcat trainingPath "AnalyzeandClean.lsp") nil)				
				(tb-btn submenuTools (ltf "SignMaker") "ImageTracer.Trace.png" (strcat trainingPath "SignMaker.lsp") nil)
				(tb-btn submenuTools (ltf "NC Reader") "DataExchange.NCReader.png" (strcat trainingPath "NCReader.lsp") nil)

		(TB-BTN grp (LTF "Variable Offset Control") (strcat (GETVAR "PATHSCRIPT") "Images/APEX60 32x36.png") (strcat trainingPath "VOC.lsp") nil)
		(TB-BTN grp (LTF "Fixed Speed (FS) Attribute") (strcat trainingPath "Images/Help.png") (strcat trainingPath "FS.lsp") nil)
		(TB-BTN grp (LTF "Height Setter (HS) Attribute") (strcat trainingPath "Images/Help.png") (strcat trainingPath "HS.lsp") nil)
		;(tb-btn grp (ltf "Height Setter Calibration (MOVE)") (strcat trainingPath "Images/Help.png") (strcat trainingPath "HeightSetterCalibrationMove.lsp") nil)		
		(tb-btn grp (ltf "Height Setter Calibration (Ikuhlu)") (strcat trainingPath "Images/Help.png") (strcat trainingPath "HeightSetterCalibrationIkuhlu.lsp") nil)
		(tb-btn grp (ltf "Waterjet 101") (strcat trainingPath "Images/WaterJetMaintenance.png") (strcat trainingPath "Waterjet101.lsp") nil)		
		(tb-btn grp (ltf "Piercing Glass \&& Stone") (strcat trainingPath "Images/WaterJetMaintenance.png") (strcat trainingPath "PiercingGlass.lsp") nil)
		(tb-btn grp (ltf "Drilling Composites") (strcat trainingPath "Images/WaterJetMaintenance.png") (strcat trainingPath "DrillingComposites.lsp") nil)		
		(tb-btn grp (ltf "Waterjet Maintenance") (strcat trainingPath "Images/WaterJetMaintenance.png") (strcat trainingPath "WaterJetMaintenance.lsp") nil)
		(tb-btn grp (ltf "Work Offsets (MOVE)") (strcat trainingPath "Images/WaterJetMaintenance.png") (strcat trainingPath "WorkOffsetsMOVE.lsp") nil)		
		(tb-btn grp (ltf "Work Offsets (Ikuhlu)") (strcat trainingPath "Images/WaterJetMaintenance.png") (strcat trainingPath "WorkOffsetsIkuhlu.lsp") nil)		


		(SETQ submenu (TB-BTN grp (LTF "Stone Cutting") (strcat trainingPath "Images/Help.png") "" nil))
			(tb-btn submenu (ltf "Sone Cutting Part 1")(strcat trainingPath "Images/Help.png") (strcat trainingPath "Stone1.lsp") nil)
			(tb-btn submenu (ltf "Sone Cutting Part 2")(strcat trainingPath "Images/Help.png") (strcat trainingPath "Stone2.lsp") nil)
			(tb-btn submenu (ltf "Sone Cutting Part 3")(strcat trainingPath "Images/Help.png") (strcat trainingPath "Stone3.lsp") nil)
			(tb-btn submenu (ltf "Sone Cutting Part 4")(strcat trainingPath "Images/Help.png") (strcat trainingPath "Stone4.lsp") nil)
			(tb-btn submenu (ltf "Sone Cutting Part 5")(strcat trainingPath "Images/Help.png") (strcat trainingPath "Stone5.lsp") nil)
			(tb-btn submenu (ltf "Sone Cutting Part 6")(strcat trainingPath "Images/Help.png") (strcat trainingPath "Stone6.lsp") nil)
			(tb-btn submenu (ltf "Sone Cutting Part 7")(strcat trainingPath "Images/Help.png") (strcat trainingPath "Stone7.lsp") nil)
			(tb-btn submenu (ltf "Sone Cutting Part 8")(strcat trainingPath "Images/Help.png") (strcat trainingPath "Stone8.lsp") nil)
;=======Apps
	(tb-btn tab (ltf "Delete Cut Orders") (strcat (GETVAR "PATHSCRIPT") "Images/DeleteCutOrders.png") "DeleteCutOrders.lsp" nil)
	(tb-btn tab (ltf "ResizeRectangle") (strcat (GETVAR "PATHSCRIPT") "Images/ResizeRectangle.png") "ResizeRectangle.lsp" nil)
	(tb-btn tab (ltf "Import \& Clean") "Cam2d2.MacMat2.png" "Import and Cleanup.lsp" nil)
	(tb-btn tab (ltf "WJ Process") (strcat (GETVAR "PATHSCRIPT") "Images/Checksum Count.png") "WJ Process.lsp" "2")
	(tb-btn tab (ltf "TAC Test Piece") (strcat (GETVAR "PATHSCRIPT") "Images/TAC Test Piece Thumb.png") "TAC Test Piece.lsp" nil)
	(tb-btn tab (ltf "Q5-Q1") (strcat (GETVAR "PATHSCRIPT") "Images/Q5-Q1-Thumb_sm.png") "Q5-Q1.lsp" nil)
	(tb-btn tab (ltf "APEX60RewindRotate") (strcat (GETVAR "PATHSCRIPT") "Images/APEX60 32x36.png") "APEX60RewindRotate.lsp" nil)

	(SETQ grp (TB-GRP tab (LTF "WARDJet Apps")))
		(TB-BTN grp (LTF "5 Fingers") (strcat (GETVAR "PATHSCRIPT") "Images/5 Fingers Thumb.png") "5 Fingers.lsp" nil)
		(TB-BTN grp (LTF "APEX 60 Kinematic Calculator") (strcat (GETVAR "PATHSCRIPT") "Images/APEX60 32x36.png") "APEX 60 Kinematic Calculator.lsp" nil)
		(TB-BTN grp (LTF "Blackjack") (strcat (GETVAR "PATHSCRIPT") "Images/Cards/Ace_Spades.png") "Blackjack.lsp" nil)
		(TB-BTN grp (LTF "CenterPartsOnSheet") (strcat (GETVAR "PATHSCRIPT") "Images/CenterPartsOnSheet.png") "CenterPartsOnSheet.lsp" nil)
		(TB-BTN grp (LTF "Checksum Count") (strcat (GETVAR "PATHSCRIPT") "Images/Checksum Count.png") "Checksum Count.lsp" nil)
		(TB-BTN grp (LTF "CSVtoOrganizer") (strcat (GETVAR "PATHSCRIPT") "CSVtoOrganizer/CSVtoOrganizer.png") "CSVtoOrganizer.lsp" nil)
		(TB-BTN grp (LTF "DeleteCutOrders") (strcat (GETVAR "PATHSCRIPT") "Images/DeleteCutOrders.png") "DeleteCutOrders.lsp" nil)
		(TB-BTN grp (LTF "DeletePartsOnSheet") (strcat (GETVAR "PATHSCRIPT") "Images/DeletePartsOnSheet.png") "DeletePartsOnSheet.lsp" nil)
		(TB-BTN grp (LTF "DogBone") (strcat (GETVAR "PATHSCRIPT") "Images/DogBone-thumb.png") "DogBone.lsp" nil)
		(TB-BTN grp (LTF "Duplicate files") (strcat (GETVAR "PATHSCRIPT") "Images/Duplicate files.png") "Duplicate files.lsp" nil)
		(TB-BTN grp (LTF "HS Crash Indicator") (strcat (GETVAR "PATHSCRIPT") "Images/HS Crash Indicator.png") "HS Crash Indicator.lsp" nil)
		(TB-BTN grp (LTF "Import and Cleanup") (strcat (GETVAR "PATHSCRIPT") "Images/Import and Cleanup.png") "Import and Cleanup.lsp" nil)
		(TB-BTN grp (LTF "Import FlowMaster ORD V6") (strcat (GETVAR "PATHSCRIPT") "Images/Import.png") "Import_ORD_V6.lsp" nil)
		(TB-BTN grp (LTF "Merge files") (strcat (GETVAR "PATHSCRIPT") "Images/Merge.png") "Merge files.lsp" nil)
		(TB-BTN grp (LTF "Multi-Sheet") (strcat (GETVAR "PATHSCRIPT") "Images/Multi-Sheet.png") "Multi-Sheet.lsp" nil)
		(TB-BTN grp (LTF "Q5-Q1") (strcat (GETVAR "PATHSCRIPT") "Images/Q5-Q1-thumb.png") "Q5-Q1.lsp" nil)
		(tb-btn grp (ltf "ResizeRectangle") (strcat (GETVAR "PATHSCRIPT") "Images/ResizeRectangle.png") "ResizeRectangle.lsp" nil)
		(tb-btn grp (ltf "TAC Test Piece") (strcat (GETVAR "PATHSCRIPT") "Images/TAC Test Piece Thumb.png") "TAC Test Piece.lsp" nil)
		(tb-btn grp (ltf "Translate CNC Files") (strcat (GETVAR "PATHSCRIPT") "Images/Translate.png") "Translate CNC Files.lsp" nil)
		(TB-BTN grp (LTF "Translate FlowMaster ORD V6") (strcat (GETVAR "PATHSCRIPT") "Images/Translate.png") "Translate_ORD_V6.lsp" nil)

		
		
;=======Water-only apps
	(tb-btn tab (ltf "Water-Only Rectangles") (strcat (GETVAR "PATHSCRIPT") "Images/Water-Only Rectangles 19x32.png") "Water-Only Rectangles R2.lsp" nil)
	(tb-btn tab (ltf "Water-Only Circles") (strcat (GETVAR "PATHSCRIPT") "Images/Water-Only Circles 30x32.png") "Water-Only Circles Rev 2.lsp" nil)
	(SETQ grp (TB-GRP tab (LTF "WARDJet Water-Only Apps")))

;========
;	    (SETQ grp (TB-GRP tab (LTF "Nest")))
;      (IF (MODULES 7)
;	      (PROGN
;	        (TB-BTN grp (LTF "Old Auto") "NEST.AutoNest.png" "NEST.AutoNestOld" nil)
;	        (TB-BTN grp (LTF "Renest sheet") "NEST.AutoNest.png" "NEST.RenestSheet" nil)))))

;"systemmenu"
;"ribbonmenu"
;"quickaccesstoolbar"
;"shortcuts"
;"commandlinearea"
;"multipledrawings"
;"orthomode"
;"zoomandpan"
;"coordinateinput"

(TB-HLP "CORE.New" "new")
(TB-HLP "CORE.Templates" "templates")
(TB-HLP "CORE.Open" "open")
(TB-HLP "CORE.OpenSamples" "openSamples")
(TB-HLP "CAD.Import" "import")
(TB-HLP "CORE.Recover" "recover")
;"recentfiles"
(TB-HLP "CORE.Save" "save")
(TB-HLP "CORE.SaveAs" "saveas")
(TB-HLP "CORE.SaveTemplate" "savetemplate")
;"undo"
;"redo"
(TB-HLP "CORE.Export" "export")
(TB-HLP "Cam2d2.BugReportSave" "Support")
(TB-HLP "CORE.Close" "close")
(TB-HLP "CORE.CloseAll" "closeall")
(TB-HLP "CORE.Plot" "plot")
(TB-HLP "CORE.Limits" "Limits")
(TB-HLP "CORE.DumpImage" "dumpimage")
(TB-HLP "CORE.Preferences" "preferences")
(TB-HLP "CORE.Password" "password")
(TB-HLP "CORE.DrawingUnits" "drawingunits")
(TB-HLP "CORE.PointStyle" "pointstyle")
(TB-HLP "CORE.Dimstyle" "dimstyle")
(TB-HLP "CORE.About" "about")
(TB-HLP "CORE.Exit" "exit")
(TB-HLP "CORE.Purge" "purge")
(TB-HLP "CORE.Status" "status")
(TB-HLP "CORE.SharedFolder" "sharedfolder")
(TB-HLP "CORE.ServiceCenter" "servicecenter")
(TB-HLP "CAD.Point" "point")
(TB-HLP "CAD.Line" "line")
(TB-HLP "CAD.Arc" "arc")
(TB-HLP "CAD.ArcCSA" "arc")
(TB-HLP "CAD.ArcSCA" "arc")
(TB-HLP "CAD.ArcSCL" "arc")
(TB-HLP "CAD.ArcSEA" "arc")
(TB-HLP "CAD.ArcCED" "arc")
(TB-HLP "CAD.ArcSER" "arc")
(TB-HLP "CAD.Circle" "circle")
(TB-HLP "CAD.Circle2P" "circle")
(TB-HLP "CAD.Circle2PR" "circle")
(TB-HLP "CAD.Circle3P" "circle")
(TB-HLP "CAD.EnclosingCircle" "circle")
(TB-HLP "CAD.Rectangle" "rectangle")
(TB-HLP "CAD.RectangleXYC" "rectangle")
(TB-HLP "CAD.RectangleBB" "rectangle")
(TB-HLP "CAD.Polyline" "polyline")
(TB-HLP "CAD.Sketch" "sketch")
(TB-HLP "CAD.Spline" "spline")
(TB-HLP "CAD.Ellipse" "ellipse")
(TB-HLP "CAD.Solid" "solid")
(TB-HLP "CAD.Hatch" "hatch")
(TB-HLP "PARAMPART.ParametricShapes" "parametricshapes")
(TB-HLP "CAD.NGon" "ngon")
(TB-HLP "CAD.Obround" "obround")
(TB-HLP "CAD.Swell" "swell")
(TB-HLP "CAD.Unswell" "unswell")
(TB-HLP "CAD.Puzzle" "puzzle")
(TB-HLP "CAD.BPoly" "boundarypoly")
(TB-HLP "CAD.Offset" "offset")
(TB-HLP "CAD.Fillet" "fillet")
(TB-HLP "CAD.Trim" "trim")
(TB-HLP "CAD.ZeroFillet" "zerofillet")
(TB-HLP "CAD.Chamfer" "chamfer")
(TB-HLP "CAD.Lengthen" "lengthen")
(TB-HLP "CAD.Extend" "extend")
(TB-HLP "CAD.Boolean" "boolean")
(TB-HLP "CAD.PolylineEditor" "polylineeditor")
(TB-HLP "CAD.Break" "break")
(TB-HLP "CAD.Erase" "erase")
(TB-HLP "CAD.Join" "join")
(TB-HLP "CORE.Layer" "layer")
(TB-HLP "CAD.Explode" "explode")
(TB-HLP "CAD.Attdef" "defineattributes")
(TB-HLP "CORE.Block" "createblock")
(TB-HLP "CORE.Insert" "insertblock")
(TB-HLP "CAD.Group" "group")
(TB-HLP "CORE.WriteBlock" "saveblock")
(TB-HLP "CAD.Move" "move")
(TB-HLP "CAD.Rotate" "rotate")
(TB-HLP "CAD.MultiCopy" "copy")
(TB-HLP "CAD.Mirror" "mirror")
(TB-HLP "CAD.Scale" "scale")
(TB-HLP "CAD.Projection" "projection")                    ; NY
(TB-HLP "CAD.SuperMove" "quickmove")
(TB-HLP "CAD.Stretch" "stretch")
(TB-HLP "CAD.Skew" "skew")
(TB-HLP "CAD.Array" "array")
(TB-HLP "CAD.Dimension" "dimension")
(TB-HLP "CAD.LinearDimension" "dimlinear")
(TB-HLP "CAD.DiameterDimension" "dimdiameter")
(TB-HLP "CAD.Text" "text")
(TB-HLP "CAD.RotatedDimension" "dimrotated")
(TB-HLP "CAD.RadiusDimension" "dimradius")
(TB-HLP "CAD.AngularDimension" "dimangular")
(TB-HLP "CAD.Leader" "dimleader")
(TB-HLP "CAD.DimStyle" "dimstyle")
(TB-HLP "CORE.pan" "pan")
(TB-HLP "CORE.ZoomExtents" "zoomextents")
(TB-HLP "CORE.Zoom" "zoom")
(TB-HLP "CORE.ZoomWindow" "zoomwindow")
(TB-HLP "CORE.ZoomObject" "display#zoomobject")           ; ÄNDRA
(TB-HLP "CORE.Color" "color")
(TB-HLP "CORE.LineType" "linetype")
(TB-HLP "CORE.LineWeight" "lineweight")
(TB-HLP "CORE.SendToBack" "sendtoback")
(TB-HLP "CORE.BringToFront" "bringtofron")
(TB-HLP "CORE.Info" "info")
(TB-HLP "CAD.Distance" "distance")
(TB-HLP "CORE.Id" "id")
(TB-HLP "CAMTools.CleanUp" "cleanup")
(TB-HLP "CAMTools.Curvefit" "curvefit")
(TB-HLP "CAMTools.EdgeFix" "edgefix")
(TB-HLP "CAMTools.ObjectReplace" "replace")
(TB-HLP "CAMTools.ContourAnalyzer" "analyze")
(TB-HLP "CAMTools.BoundaryScan" "boundaryscan")
(TB-HLP "CAMTools.BoundaryTrim" "boundarytrim")
(TB-HLP "CAMTools.PolyJoint" "polyjoint")
(TB-HLP "CAMTools.CornerCutout" "cornercutout")           ;NY
(TB-HLP "CAMTools.Vectorize" "vectorize")
(TB-HLP "CAMTools.Divide" "divide")                       ;NY
(TB-HLP "CAD.pocketing" "pocketing")
(TB-HLP "CAMTools.ConvexHull" "convexhull")
(TB-HLP "CAMTools.Align" "align")
(TB-HLP "CAMTools.Dovetail" "dovetail")
(TB-HLP "SignMaker.FontTracer" "fonttracer")
(TB-HLP "CAD.Image" "image")
(TB-HLP "Imagetracer.Trace" "imagetracer")
(TB-HLP "SignMaker.Tilemaker" "tilemaker")
(TB-HLP "NEST.TileCut" "tilecut")
(TB-HLP "NEST.Inlay" "inlay")
(TB-HLP "DataExchange.NCReader" "ncreader")
(TB-HLP "CORE.Custom" "custom")
(TB-HLP "Cam2d2.CameraSnapshot" "CameraSnapshot")
(TB-HLP "Cam2d2.CameraCalibration" "CameraCalibration")
(TB-HLP "Cam2d2.MacMat2" "selectsetup")
(TB-HLP "Cam2d2.MachineSetup" "machinesetup")
(TB-HLP "Cam2d2.MaterialSetup" "material")
(TB-HLP "Cam2d2.CreateSheet" "sheetcreate")
(TB-HLP "Cam2d2.SubSheet" "sheetfromhole")
(TB-HLP "Cam2d2.LockSheet" "sheetlock")
(TB-HLP "Cam2d2.UnlockSheet" "sheetunlock")
(TB-HLP "Cam2d2.DivideSheet" "sheetdivide")
(TB-HLP "Cam2d2.OpenSheetAdd" "sheetexport")
(TB-HLP "Cam2d2.OpenSheet" "sheetopen")
(TB-HLP "Cam2d2.History" "sheethistory")
(TB-HLP "Cam2d2.SheetInventory" "sheetinventory")
(TB-HLP "Cam2d2.ImportSheet" "sheetmigrate")
(TB-HLP "Cam2d2.CreatePart" "createpart")
(TB-HLP "Cam2d2.Quality" "quality")
(TB-HLP "Cam2d2.ToolSetup" "toolsetup")
(TB-HLP "Cam2d2.PartProperties" "partproperties")
(TB-HLP "Cam2d2.PartText" "parttext")
(TB-HLP "Cam2d2.Inkjet" "inkjet")                         ; NY
(TB-HLP "Cam2d2.PartBrowser" "partbrowser")
(TB-HLP "Cam2d2.JoinParts" "joinparts")
(TB-HLP "Cam2d2.SplitParts" "splitparts")
(TB-HLP "Cam2d2.ClonePart" "clonepart")
(TB-HLP "Cam2d2.View3d" "viewin3d")
(TB-HLP "Cam2d2.ContourCut" "contour")
(TB-HLP "Cam2d2.Quick" "quickcut")
(TB-HLP "Cam2d2.Marking" "marking")
(TB-HLP "Cam2d2.Holes" "holes")
(TB-HLP "Cam2d2.Manual" "manualcut")
(TB-HLP "Cam2d2.Bridges" "bridges")
(TB-HLP "Cam2d2.CommonCutlines" "commoncutline")
(TB-HLP "Cam2d2.Cutoff" "cutoff")
(TB-HLP "Cam2d2.BreakToolpath" "breaktoolpath")
(TB-HLP "Cam2d2.CloneCutting" "clonetoolpath")
(TB-HLP "Cam2d2.EditPart" "edittoolpath")
(TB-HLP "Cam2d2.RemoveCutting" "erasetoolpath")
(TB-HLP "Cam2d2.MicroJoints" "microjoints")
(TB-HLP "Cam2d2.ChainCutting" "chaincutting")
(TB-HLP "Cam2d2.DisconnectToolpath" "disconnect")
(TB-HLP "Cam2d2.defineBevel" "definebevel")
(TB-HLP "Cam2d2.BevelCut" "cutbevel")
(TB-HLP "Cam2d2.Quickbevel" "quickbevel")
(TB-HLP "TUBE.Tube2" "tube")
(TB-HLP "Cam2d2.CutOrder" "cutorder")
(TB-HLP "Cam2d2.Process2" "process")
(TB-HLP "Cam2d2.CuttingParameters" "cuttingparameters")
(TB-HLP "Cam2d2.MachineMethod" "strategy")
(TB-HLP "ORGANIZER.Register" "register")
(TB-HLP "ORGANIZER.Organizer" "organizer")
(TB-HLP "NEST.BumpNest" "quicknest")
(TB-HLP "NEST.BumpNestGlide" "glidenest")                   ; NY
(TB-HLP "NEST.SingleNest" "singlenest")
(TB-HLP "NEST.Rectangle" "rectanglenest")                   ; NY
(TB-HLP "NEST.Circle" "circlenest")                         ; NY
(TB-HLP "NEST.AutoNest" "autonest")
(TB-HLP "NEST.Report" "nestreport")

(foreach file (file-findall "." "*.tb")
    (load file))
(IF ltflist (LTFSAVE))
